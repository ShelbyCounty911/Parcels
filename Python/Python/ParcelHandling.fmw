FME workspace ParcelHandling.fmw

Parameters:
- SourcesGrouping =   # Data Sources
- SourceTXT = C:\Automation\ParcelHandling\Data\LEGDAT.txt   # Source Text File
- ProductionGDB = \\sc911-gis01\gis\Data\Production.gdb   # Production File Geodatabase
- CertParcelsGDB = \\sc911-gis01\gis\Data\Parcels\Cert2025.gdb   # Certified Parcels File Geodatabase

Readers:
- TEXTLINE_1: TEXTLINE from $(SourceTXT)
- GEODATABASE_FILE_2: GEODATABASE_FILE from $(ProductionGDB)
- GEODATABASE_FILE_4: GEODATABASE_FILE from \\sc911-gis01\gis\Data\Production.gdb
- GEODATABASE_FILE_1: GEODATABASE_FILE from $(CertParcelsGDB)

Writers:
- GEODATABASE_FILE_3: GEODATABASE_FILE to \\sc911-gis01\gis\Data\Production.gdb
- GEODATABASE_FILE_6: GEODATABASE_FILE to \\sc911-gis01\gis\Data\Production.gdb

Note: Parcel ID C0243 00656 is not making it through. It's not getting joined
Note: Future work / parAddress needs to be populated / Assign a weighted metrix based on the structure type field with the value 1 = house being the highest

Bookmark: Source: LEGDAT Text File
text_line (reader TEXTLINE_1)
    attributes: text_line_data buffer
    -> Junction_2

Bookmark: Extract Subd Name
Note: Import source data. Looking for comma delimited text file sent by the assessor's office. Change format as needed
Junction_2
    -> Subd_Name_Replacement
Note: Find erratic strings in subdivision names and replace them with standardized versions (or remove them). / Examples: / - Convert roman numerals and ordinal numbers to integers / - Use regex to remove scenarios like "Phase 1"
Note: Import both parcel GIS files and the LEGDAT text file provided by the assessor's office. Prep the data from both sources, and then do a match based on a common attribute (parcel ID), then override existing subd names from the GIS parcels with the ones sent in the text file
Subd_Name_Replacement: Subd Name Replacement
    TEXT_LINE_DATA = @Value(text_line_data)
    -> Subd_Name_Cleaners
Note: Then use regex expressions to remove all other unnecessary parts of subdivision names. Heavy use of regex and loops.
Subd_Name_Cleaners: Subd Name Cleaners
    TEXT_LINE_DATA = @Value(text_line_data)
    _SUBDNAME = @Value(_SubdName)
    -> Title_Case
Note: Finally, convert subdivision names to Full Title Case. Deal with exceptions like the D in "McDonalds"
Title_Case: Title Case
    _SUBDNAME = @Value(_SubdName)
    -> Clean_up_ParcelID
Clean_up_ParcelID: Clean up ParcelID
    _PARCELID = @Value(_ParcelID)
    -> Join_Parcels [LEFT]
Note: Remove extra spaces
Prep_Source_Parcels: Prep Source Parcels
    PCOMMENTS = @Value(pcomments)
    PEFFECTIVE = @Value(peffective)
    PEXPIRE = @Value(pexpire)
    PEXTRESRCE = @Value(pextResrce)
    PGCEDITBY = @Value(pgcEditBy)
    PGCEXCEPTION = @Value(pgcException)
    PGCLABEL = @Value(pgcLabel)
    PGCMODDATE = @Value(pgcModDate)
    PGCMODTYPE = @Value(pgcModType)
    PGCUNQID = @Value(pgcUnqID)
    POBJECTID = @Value(pOBJECTID)
    PPARADD = @Value(pparAdd)
    PPARNUM = @Value(pparNum)
    PPAROWN = @Value(pparOwn)
    PPAROWN2 = @Value(pparOwn2)
    PPAROWNADD = @Value(pparOwnAdd)
    PPAROWNTEL = @Value(pparOwnTel)
    PPARSTREET = @Value(pparStreet)
    PPARTYPE = @Value(pparType)
    PSHAPE_AREA = @Value(pShape_Area)
    PSHAPE_LENGTH = @Value(pShape_Length)
    PSRCLASTEDT = @Value(psrcLastEdt)
    PSRCOFDATA = @Value(psrcOfData)
    PSRCUNQID = @Value(psrcUnqID)
    PUPLOADAUTH = @Value(puploadAuth)
    PUPLOADDATE = @Value(puploadDate)
    -> Join_Parcels [RIGHT]
Note: Join based on common ParcelID
Join_Parcels: FeatureJoiner
    ATTR_CONFLICT_RES = USE_LEFT
    GEOMETRY_HANDLING = USE_RIGHT
    JOIN_KEYS = _ParcelID psrcUnqID AUTO
    JOIN_MODE = Inner
    JOINED -> AttributeManager
Note: Organize and rename fields as needed
AttributeManager
    ATTR_TABLE:
      RENAME_SET_VALUE pOBJECTID > OBJECTID (int32)
      REMOVE _ParcelID (varchar(200))
      RENAME_SET_VALUE _SubdName > SubdName (varchar(200))
      RENAME_SET_VALUE psrcOfData > Source (varchar(75))
      RENAME_SET_VALUE psrcLastEdt > EditDate (datetime)
      RENAME_SET_VALUE puploadAuth > UploadAuth (varchar(75))
      RENAME_SET_VALUE puploadDate > UploadDate (datetime)
      RENAME_SET_VALUE peffective > Effective (datetime)
      RENAME_SET_VALUE pexpire > Expire (datetime)
      RENAME_SET_VALUE pparOwn > ParOwn (varchar(150))
      RENAME_SET_VALUE pparOwn2 > ParOwn2 (varchar(150))
      RENAME_SET_VALUE pparOwnAdd > ParOwn3 (varchar(150))
      RENAME_SET_VALUE pparOwnTel > ParOwnTel (varchar(15))
      RENAME_SET_VALUE pparAdd > ParAddress (varchar(150))
      RENAME_SET_VALUE pparNum > ParStNum (int32)
      RENAME_SET_VALUE pparStreet > ParStName (varchar(100))
      RENAME_SET_VALUE pparType > ParStType (varchar(100))
      RENAME_SET_VALUE pextResrce > ExtResrce (varchar(254))
      RENAME_SET_VALUE pcomments > Comments (varchar(100))
      RENAME_SET_VALUE psrcUnqID > ParcelID (varchar(100))
      REMOVE pgcModDate (datetime)
      REMOVE pgcLabel (varchar(150))
      REMOVE pgcUnqID (varchar(38))
      REMOVE pgcModType (varchar(2))
      REMOVE pgcEditBy (varchar(100))
      REMOVE pgcException (varchar(75))
      REMOVE text_line_data (buffer)
      REMOVE _ParcelInfo{} (varchar(200))
      REMOVE _element_count (uint64)
    USER_EXPOSED_ATTRIBUTES = pShape.STLength(),pShape.STArea()
    -> Filter_Out_Invalid
Note: If any parcels come through with no parcel ID, exclude them, otherwise, procceed to the writer
Filter_Out_Invalid: Tester
    BOOL_OP = COMPOSITE
    COMPOSITE_TEST = NOT ( 1 OR 2 OR 3 OR 4 OR 5 )
    TEST_CLAUSE:
      TEST ParcelID ATTRIBUTE_VALUE_NULL ""
      TEST ParcelID ATTRIBUTE_IS_EMPTY ""
      TEST ParcelID ATTRIBUTE_IS_MISSING ""
      TEST @Value(ParcelID) =
      TEST @Value(ParcelID) =
    TEST_MODE = TEST
    PASSED -> Change_Detector [REVISED]
    PASSED -> Parcels_Curated (writer GEODATABASE_FILE_3)
Note: Bring in the existing parcels for a comparison
Junction_3
    -> Change_Detector [ORIGINAL]
Note: Compare against existing and ignore everything that's exactly the same. This way only new/changed features are processed. This improves performance exponentially
Change_Detector: ChangeDetector
    BLANK_AND_MISSING_DIFFER = No
    CHECK_COORDINATE_SYSTEMS = No
    CHECK_TYPES_AND_ENCODINGS = No
    LENIENT_MATCH = Yes
    MATCH = 2D
    MATCHATTRS = Comments EditDate Effective Expire ExtResrce OBJECTID ParAddress ParOwn ParOwn2 ParOwn3 ParOwnTel ParStName ParStNum ParStType ParcelID Source SubdName UploadAuth UploadDate Shape_Area Shape_Length
    MATCH_STRATEGY_LOOKUP = MATCH
    UNCHANGED_OUTPUT_LOOKUP = ORIGINAL
    UPSERT_MODE = No
    MATCH_STRATEGY = Match Selected Attributes
    UNCHANGED_OUTPUT = Output Original
    INSERTED -> Parcels_Curated (writer GEODATABASE_FILE_3)

Bookmark: Source: Certified Parcels
Cert_Parcels_2025 (reader GEODATABASE_FILE_1)
    attributes: OBJECTID integer, MAP char(5), PARCELID char(15), PARID char(30), OWNER char(40), OWNER_EXT char(40), OWN_ADRNO double, OWN_ADRPREDIR char(2), OWN_ADRSTR char(30), OWN_ADRSUF char(8), OWN_ADRPOSTDIR char(5), OWN_CITY char(40), OWN_STATE char(2), OWN_UNITDESC char(10), OWN_UNITNO char(10), OWN_ADDR1 char(80), OWN_ADDR2 char(80), OWN_ADDR3 char(80), OWN_ZIP char(5), OWN_ZIP4 char(4), OWN_NOTE1 char(40), OWN_NOTE2 char(40), PAR_ALTID char(30), PAR_ADRNO double, PAR_ADRADD char(6), PAR_ADRPREDIR char(2), PAR_ADRSTR char(30), PAR_ADRSUF char(8), PAR_ADRPOSTDIR char(5), PAR_UNITDESC char(10),
      PAR_UNITNO char(10), NBHD char(8), CLASS char(4), LUC char(4), LIVUNIT char(3), ZONING char(8), PAR_NOTE1 char(40), PAR_NOTE2 char(40), PAR_ZIP char(5), PAR_ADDR1 char(80), TPARCEL char(30), PAID char(30), LANDUSE char(50), MUNI char(30), Longitude double, Latitude double, TAXYR integer, Shape_Length double, Shape_Area double
    -> Junction_4

Bookmark: Update Parcels in Production
Note: Import new certified source parcels
Junction_4
    -> Parcel_Number_Cleaner
    -> cert_source_parcels_renamer
Note: Rename the new field names of the new parcels to make them easier to identify
cert_source_parcels_renamer: BulkAttributeRenamer
    ATTRCHOICE_ACTION = NONPROTECTEDFME
    MODE_CHOICE = RENAME
    PATTERN_ACTION_DISP = ADDPREFIX
    REPLACE_STR = csp
    ATTRCHOICE = All Attributes
    -> parcels_ETL_attr_mngr
Note: Manage field mapping
parcels_ETL_attr_mngr: AttributeManager
    ATTR_TABLE:
      RENAME_SET_VALUE cspPARCELID > srcUnqID (varchar(20))
      SET_TO comments (varchar(100)) = FME_CONDITIONAL:DEFAULT_VALUE'_FME_NO_OP_'BOOL_OP;COMPOSITE;COMPOSITE_TEST;( 1 OR 2 OR 3 ) AND ( 4 OR 5 OR 6 );TEST cspPAR_NOTE1 ATTRIBUTE_VALUE_NULL _FME_BLANK_STRING_;TEST cspPAR_NOTE1 ATTRIBUTE_IS_EMPTY _FME_BLANK_STRING_;TEST cspPAR_NOTE1 ATTRIBUTE_IS_MISSING _FME_BLANK_STRING_;TEST cspOWN_NOTE2 ATTRIBUTE_VALUE_NULL _FME_BLANK_STRING_;TEST cspOWN_NOTE2 ATTRIBUTE_IS_EMPTY _FME_BLANK_STRING_;TEST cspOWN_NOTE2 ATTRIBUTE_IS_MISSING _FME_BLANK_STRING_'_FME_NO_OP_'BOOL_OP;COMPOSITE;COMPOSITE_TEST;( 1 OR 2 OR 3 ) AND NOT ( 4 OR 5 OR 6 );TEST cspPAR_NOTE1 ATTRIBUTE_VALUE_NULL _FME_BLANK_STRING_;TEST cspPAR_NOTE1 ATTRIBUTE_IS_EMPTY _FME_BLANK_STRING_;TEST cspPAR_NOTE1 ATTRIBUTE_IS_MISSING _FME_BLANK_STRING_;TEST cspOWN_NOTE2 ATTRIBUTE_VALUE_NULL _FME_BLANK_STRING_;TEST cspOWN_NOTE2 ATTRIBUTE_IS_EMPTY _FME_BLANK_STRING_;TEST cspOWN_NOTE2 ATTRIBUTE_IS_MISSING _FME_BLANK_STRING_'@Value(cspPAR_NOTE2)'BOOL_OP;COMPOSITE;COMPOSITE_TEST;NOT ( 1 OR 2 OR 3 ) AND ( 4 OR 5 OR 6 );TEST cspPAR_NOTE1 ATTRIBUTE_VALUE_NULL _FME_BLANK_STRING_;TEST cspPAR_NOTE1 ATTRIBUTE_IS_EMPTY _FME_BLANK_STRING_;TEST cspPAR_NOTE1 ATTRIBUTE_IS_MISSING _FME_BLANK_STRING_;TEST cspOWN_NOTE2 ATTRIBUTE_VALUE_NULL _FME_BLANK_STRING_;TEST cspOWN_NOTE2 ATTRIBUTE_IS_EMPTY _FME_BLANK_STRING_;TEST cspOWN_NOTE2 ATTRIBUTE_IS_MISSING _FME_BLANK_STRING_'@Value(cspPAR_NOTE1)'FME_NUM_CONDITIONS4___
      SET_TO effective (datetime) = @DateTimeNow()
      SET_TO expire (datetime) = 20991231
      SET_TO extResrce (varchar(254)) = [Property Record](<https://www.assessormelvinburgess.com/gis?parcelid=@Value(srcUnqID)>)
      SET_TO gcLabel (varchar(150)) = @FullTitleCase(@Value(cspOWNER))
      SET_TO gcModDate (datetime) = @DateTimeNow()
      SET_TO parAdd (varchar(150)) = FME_CONDITIONAL:DEFAULT_VALUE'_FME_NO_OP_'BOOL_OP;COMPOSITE;COMPOSITE_TEST;1 AND ( 2 AND 3 AND 4 AND 5 );TEST cspPAR_ADRNO ATTRIBUTE_HAS_A_VALUE _FME_BLANK_STRING_;TEST cspPAR_ADRPREDIR ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR ATTRIBUTE_HAS_A_VALUE _FME_BLANK_STRING_'@Value(cspPAR_ADRNO) @Value(cspPAR_ADRPREDIR) @Value(cspPAR_ADRSTR) @Value(cspPAR_ADRSUF) @Value(cspPAR_ADRPOSTDIR)'BOOL_OP;COMPOSITE;COMPOSITE_TEST;1 AND ( NOT 2 AND 3 AND 4 AND 5 );TEST cspPAR_ADRNO ATTRIBUTE_HAS_A_VALUE _FME_BLANK_STRING_;TEST cspPAR_ADRPREDIR ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR ATTRIBUTE_HAS_A_VALUE _FME_BLANK_STRING_'@Value(cspPAR_ADRNO) @Value(cspPAR_ADRSTR) @Value(cspPAR_ADRSUF) @Value(cspPAR_ADRPOSTDIR)'BOOL_OP;COMPOSITE;COMPOSITE_TEST;1 AND ( 2 AND 3 AND 4 AND 5 );TEST cspPAR_ADRNO ATTRIBUTE_HAS_A_VALUE _FME_BLANK_STRING_;TEST cspPAR_ADRPREDIR ATTRIBUTE_HAS_A_VALUE _FME_BLANK_STRING_;TEST cspPAR_ADRSTR ATTRIBUTE_HAS_A_VALUE _FME_BLANK_STRING_;TEST cspPAR_ADRSUF NOT_ATTRIBUTE_HAS_A_VALUE _FME_BLANK_STRING_;TEST cspPAR_ADRPOSTDIR ATTRIBUTE_HAS_A_VALUE _FME_BLANK_STRING_'@Value(cspPAR_ADRNO) @Value(cspPAR_ADRPREDIR) @Value(cspPAR_ADRSTR) @Value(cspPAR_ADRPOSTDIR)'BOOL_OP;COMPOSITE;COMPOSITE_TEST;1 AND ( 2 AND 3 AND 4 AND 5 );TEST cspPAR_ADRNO ATTRIBUTE_HAS_A_VALUE _FME_BLANK_STRING_;TEST cspPAR_ADRPREDIR ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR NOT_ATTRIBUTE_HAS_A_VALUE _FME_BLANK_STRING_'@Value(cspPAR_ADRNO) @Value(cspPAR_ADRPREDIR) @Value(cspPAR_ADRSTR) @Value(cspPAR_ADRSUF)'BOOL_OP;COMPOSITE;COMPOSITE_TEST;1 AND ( NOT 2 AND 3 AND 4 AND 5 );TEST cspPAR_ADRNO ATTRIBUTE_HAS_A_VALUE _FME_BLANK_STRING_;TEST cspPAR_ADRPREDIR ATTRIBUTE_HAS_A_VALUE _FME_BLANK_STRING_;TEST cspPAR_ADRSTR ATTRIBUTE_HAS_A_VALUE _FME_BLANK_STRING_;TEST cspPAR_ADRSUF NOT_ATTRIBUTE_HAS_A_VALUE _FME_BLANK_STRING_;TEST cspPAR_ADRPOSTDIR ATTRIBUTE_HAS_A_VALUE _FME_BLANK_STRING_'@Value(cspPAR_ADRNO) @Value(cspPAR_ADRSTR) @Value(cspPAR_ADRPOSTDIR)'BOOL_OP;COMPOSITE;COMPOSITE_TEST;1 AND (NOT 2 AND 3 AND 4 AND 5 );TEST cspPAR_ADRNO ATTRIBUTE_HAS_A_VALUE _FME_BLANK_STRING_;TEST cspPAR_ADRPREDIR ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR NOT_ATTRIBUTE_HAS_A_VALUE _FME_BLANK_STRING_'@Value(cspPAR_ADRNO) @Value(cspPAR_ADRSTR) @Value(cspPAR_ADRSUF)'BOOL_OP;COMPOSITE;COMPOSITE_TEST;1 AND ( 2 AND 3 AND 4 AND 5 );TEST cspPAR_ADRNO ATTRIBUTE_HAS_A_VALUE _FME_BLANK_STRING_;TEST cspPAR_ADRPREDIR ATTRIBUTE_HAS_A_VALUE _FME_BLANK_STRING_;TEST cspPAR_ADRSTR ATTRIBUTE_HAS_A_VALUE _FME_BLANK_STRING_;TEST cspPAR_ADRSUF NOT_ATTRIBUTE_HAS_A_VALUE _FME_BLANK_STRING_;TEST cspPAR_ADRPOSTDIR NOT_ATTRIBUTE_HAS_A_VALUE _FME_BLANK_STRING_'@Value(cspPAR_ADRNO) @Value(cspPAR_ADRPREDIR) @Value(cspPAR_ADRSTR)'FME_NUM_CONDITIONS8___
      SET_TO parNum (int32) = FME_CONDITIONAL:DEFAULT_VALUE'@Value(cspPAR_ADRNO)'BOOL_OP;OR;COMPOSITE_TEST;1 OR 2 OR 3 OR 4 OR 5;TEST cspPAR_ADRNO ATTRIBUTE_VALUE_NULL _FME_BLANK_STRING_;TEST cspPAR_ADRNO ATTRIBUTE_IS_EMPTY _FME_BLANK_STRING_;TEST cspPAR_ADRNO ATTRIBUTE_IS_MISSING _FME_BLANK_STRING_;TEST @Value(cspPAR_ADRNO) =  ;TEST @Value(cspPAR_ADRNO) = 0'0'FME_NUM_CONDITIONS2___
      SET_TO parOwn (varchar(150)) = @FullTitleCase(@Value(cspOWNER))
      SET_TO parOwn2 (varchar(150)) = @FullTitleCase(@Value(cspOWNER_EXT))
      SET_TO parOwnAdd (varchar(150)) = FME_CONDITIONAL:DEFAULT_VALUE'_FME_NO_OP_'BOOL_OP;COMPOSITE;COMPOSITE_TEST;1 AND ( 2 AND 3 AND 4 AND 5 );TEST cspOWN_ADRNO ATTRIBUTE_HAS_A_VALUE _FME_BLANK_STRING_;TEST cspOWN_ADRPREDIR ATTRIBUTE_HAS_A_VALUE _FME_BLANK_STRING_;TEST cspOWN_ADRSTR ATTRIBUTE_HAS_A_VALUE _FME_BLANK_STRING_;TEST cspOWN_ADRSUF ATTRIBUTE_HAS_A_VALUE _FME_BLANK_STRING_;TEST cspOWN_ADRPOSTDIR ATTRIBUTE_HAS_A_VALUE _FME_BLANK_STRING_'@Value(cspOWN_ADRNO) @Value(cspOWN_ADRPREDIR) @Value(cspOWN_ADRSTR) @Value(cspOWN_ADRSUF) @Value(cspOWN_ADRPOSTDIR)'BOOL_OP;COMPOSITE;COMPOSITE_TEST;1 AND ( NOT 2 AND 3 AND 4 AND 5 );TEST cspOWN_ADRNO ATTRIBUTE_HAS_A_VALUE _FME_BLANK_STRING_;TEST cspOWN_ADRPREDIR ATTRIBUTE_HAS_A_VALUE _FME_BLANK_STRING_;TEST cspOWN_ADRSTR ATTRIBUTE_HAS_A_VALUE _FME_BLANK_STRING_;TEST cspOWN_ADRSUF ATTRIBUTE_HAS_A_VALUE _FME_BLANK_STRING_;TEST cspOWN_ADRPOSTDIR ATTRIBUTE_HAS_A_VALUE _FME_BLANK_STRING_'@Value(cspOWN_ADRNO) @Value(cspOWN_ADRSTR) @Value(cspOWN_ADRSUF) @Value(cspOWN_ADRPOSTDIR)'BOOL_OP;COMPOSITE;COMPOSITE_TEST;1 AND ( 2 AND 3 AND 4 AND 5 );TEST cspOWN_ADRNO ATTRIBUTE_HAS_A_VALUE _FME_BLANK_STRING_;TEST cspOWN_ADRPREDIR ATTRIBUTE_HAS_A_VALUE _FME_BLANK_STRING_;TEST cspOWN_ADRSTR ATTRIBUTE_HAS_A_VALUE _FME_BLANK_STRING_;TEST cspOWN_ADRSUF NOT_ATTRIBUTE_HAS_A_VALUE _FME_BLANK_STRING_;TEST cspOWN_ADRPOSTDIR ATTRIBUTE_HAS_A_VALUE _FME_BLANK_STRING_'@Value(cspOWN_ADRNO) @Value(cspOWN_ADRPREDIR) @Value(cspOWN_ADRSTR) @Value(cspOWN_ADRPOSTDIR)'BOOL_OP;COMPOSITE;COMPOSITE_TEST;1 AND ( 2 AND 3 AND 4 AND 5 );TEST cspOWN_ADRNO ATTRIBUTE_HAS_A_VALUE _FME_BLANK_STRING_;TEST cspOWN_ADRPREDIR ATTRIBUTE_HAS_A_VALUE _FME_BLANK_STRING_;TEST cspOWN_ADRSTR ATTRIBUTE_HAS_A_VALUE _FME_BLANK_STRING_;TEST cspOWN_ADRSUF ATTRIBUTE_HAS_A_VALUE _FME_BLANK_STRING_;TEST cspOWN_ADRPOSTDIR NOT_ATTRIBUTE_HAS_A_VALUE _FME_BLANK_STRING_'@Value(cspOWN_ADRNO) @Value(cspOWN_ADRPREDIR) @Value(cspOWN_ADRSTR) @Value(cspOWN_ADRSUF)'BOOL_OP;COMPOSITE;COMPOSITE_TEST;1 AND ( NOT 2 AND 3 AND 4 AND 5 );TEST cspOWN_ADRNO ATTRIBUTE_HAS_A_VALUE _FME_BLANK_STRING_;TEST cspOWN_ADRPREDIR ATTRIBUTE_HAS_A_VALUE _FME_BLANK_STRING_;TEST cspOWN_ADRSTR ATTRIBUTE_HAS_A_VALUE _FME_BLANK_STRING_;TEST cspOWN_ADRSUF NOT_ATTRIBUTE_HAS_A_VALUE _FME_BLANK_STRING_;TEST cspOWN_ADRPOSTDIR ATTRIBUTE_HAS_A_VALUE _FME_BLANK_STRING_'@Value(cspOWN_ADRNO) @Value(cspOWN_ADRSTR) @Value(cspOWN_ADRPOSTDIR)'BOOL_OP;COMPOSITE;COMPOSITE_TEST;1 AND (NOT 2 AND 3 AND 4 AND 5 );TEST cspOWN_ADRNO ATTRIBUTE_HAS_A_VALUE _FME_BLANK_STRING_;TEST cspOWN_ADRPREDIR ATTRIBUTE_HAS_A_VALUE _FME_BLANK_STRING_;TEST cspOWN_ADRSTR ATTRIBUTE_HAS_A_VALUE _FME_BLANK_STRING_;TEST cspOWN_ADRSUF ATTRIBUTE_HAS_A_VALUE _FME_BLANK_STRING_;TEST cspOWN_ADRPOSTDIR NOT_ATTRIBUTE_HAS_A_VALUE _FME_BLANK_STRING_'@Value(cspOWN_ADRNO) @Value(cspOWN_ADRSTR) @Value(cspOWN_ADRSUF)'BOOL_OP;COMPOSITE;COMPOSITE_TEST;1 AND ( 2 AND 3 AND 4 AND 5 );TEST cspOWN_ADRNO ATTRIBUTE_HAS_A_VALUE _FME_BLANK_STRING_;TEST cspOWN_ADRPREDIR ATTRIBUTE_HAS_A_VALUE _FME_BLANK_STRING_;TEST cspOWN_ADRSTR ATTRIBUTE_HAS_A_VALUE _FME_BLANK_STRING_;TEST cspOWN_ADRSUF NOT_ATTRIBUTE_HAS_A_VALUE _FME_BLANK_STRING_;TEST cspOWN_ADRPOSTDIR NOT_ATTRIBUTE_HAS_A_VALUE _FME_BLANK_STRING_'@Value(cspOWN_ADRNO) @Value(cspOWN_ADRPREDIR) @Value(cspOWN_ADRSTR)'FME_NUM_CONDITIONS8___
      SET_TO parStreet (varchar(100)) = FME_CONDITIONAL:DEFAULT_VALUE'@Value(cspPAR_ADRSTR)'BOOL_OP;AND;COMPOSITE_TEST;1 AND 2 AND 3 AND 4;TEST cspPAR_ADRPREDIR ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR ATTRIBUTE_HAS_A_VALUE _FME_BLANK_STRING_'@Value(cspPAR_ADRPREDIR) @Value(cspPAR_ADRSTR) @Value(cspPAR_ADRSUF) @Value(cspPAR_ADRPOSTDIR)'BOOL_OP;AND;COMPOSITE_TEST;1 AND 2 AND 3 AND 4;TEST cspPAR_ADRPREDIR NOT_ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR ATTRIBUTE_HAS_A_VALUE _FME_BLANK_STRING_'@Value(cspPAR_ADRSTR) @Value(cspPAR_ADRSUF) @Value(cspPAR_ADRPOSTDIR)'BOOL_OP;AND;COMPOSITE_TEST;1 AND 2 AND 3 AND 4;TEST cspPAR_ADRPREDIR ATTRIBUTE_HAS_A_VALUE _FME_BLANK_STRING_;TEST cspPAR_ADRSTR ATTRIBUTE_HAS_A_VALUE _FME_BLANK_STRING_;TEST cspPAR_ADRSUF NOT_ATTRIBUTE_HAS_A_VALUE _FME_BLANK_STRING_;TEST cspPAR_ADRPOSTDIR ATTRIBUTE_HAS_A_VALUE _FME_BLANK_STRING_'@Value(cspPAR_ADRPREDIR) @Value(cspPAR_ADRSTR) @Value(cspPAR_ADRPOSTDIR)'BOOL_OP;AND;COMPOSITE_TEST;1 AND 2 AND 3 AND 4;TEST cspPAR_ADRPREDIR ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR NOT_ATTRIBUTE_HAS_A_VALUE _FME_BLANK_STRING_'@Value(cspPAR_ADRPREDIR) @Value(cspPAR_ADRSTR) @Value(cspPAR_ADRSUF)'BOOL_OP;AND;COMPOSITE_TEST;1 AND 2 AND 3 AND 4;TEST cspPAR_ADRPREDIR NOT_ATTRIBUTE_HAS_A_VALUE _FME_BLANK_STRING_;TEST cspPAR_ADRSTR ATTRIBUTE_HAS_A_VALUE _FME_BLANK_STRING_;TEST cspPAR_ADRSUF NOT_ATTRIBUTE_HAS_A_VALUE _FME_BLANK_STRING_;TEST cspPAR_ADRPOSTDIR ATTRIBUTE_HAS_A_VALUE _FME_BLANK_STRING_'@Value(cspPAR_ADRSTR) @Value(cspPAR_ADRPOSTDIR)'BOOL_OP;AND;COMPOSITE_TEST;1 AND 2 AND 3 AND 4;TEST cspPAR_ADRPREDIR NOT_ATTRIBUTE_HAS_A_VALUE _FME_BLANK_STRING_;TEST cspPAR_ADRSTR ATTRIBUTE_HAS_A_VALUE _FME_BLANK_STRING_;TEST cspPAR_ADRSUF ATTRIBUTE_HAS_A_VALUE _FME_BLANK_STRING_;TEST cspPAR_ADRPOSTDIR NOT_ATTRIBUTE_HAS_A_VALUE _FME_BLANK_STRING_'@Value(cspPAR_ADRSTR) @Value(cspPAR_ADRSUF)'BOOL_OP;AND;COMPOSITE_TEST;1 AND 2 AND 3 AND 4;TEST cspPAR_ADRPREDIR ATTRIBUTE_HAS_A_VALUE _FME_BLANK_STRING_;TEST cspPAR_ADRSTR ATTRIBUTE_HAS_A_VALUE _FME_BLANK_STRING_;TEST cspPAR_ADRSUF NOT_ATTRIBUTE_HAS_A_VALUE _FME_BLANK_STRING_;TEST cspPAR_ADRPOSTDIR NOT_ATTRIBUTE_HAS_A_VALUE _FME_BLANK_STRING_'@Value(cspPAR_ADRPREDIR) @Value(cspPAR_ADRSTR)'FME_NUM_CONDITIONS8___
      SET_TO srcLastEdt (datetime) = @DateTimeNow()
      SET_TO srcOfData (varchar(75)) = Shelby County Assessor of Property
      SET_TO uploadAuth (varchar(75)) = Shelby County 911
      SET_TO uploadDate (datetime) = @DateTimeNow()
      REMOVE cspOBJECTID (int32)
      REMOVE cspMAP (varchar(5))
      REMOVE cspPARID (varchar(30))
      REMOVE cspOWNER (varchar(40))
      REMOVE cspOWNER_EXT (varchar(40))
      REMOVE cspOWN_ADRNO (real64)
      REMOVE cspOWN_ADRPREDIR (varchar(2))
      REMOVE cspOWN_ADRSTR (varchar(30))
      REMOVE cspOWN_ADRSUF (varchar(8))
      REMOVE cspOWN_ADRPOSTDIR (varchar(5))
      REMOVE cspOWN_CITY (varchar(40))
      REMOVE cspOWN_STATE (varchar(2))
      REMOVE cspOWN_UNITDESC (varchar(10))
      REMOVE cspOWN_UNITNO (varchar(10))
      REMOVE cspOWN_ADDR1 (varchar(80))
      REMOVE cspOWN_ADDR2 (varchar(80))
      REMOVE cspOWN_ADDR3 (varchar(80))
      REMOVE cspOWN_ZIP (varchar(5))
      REMOVE cspOWN_ZIP4 (varchar(4))
      REMOVE cspOWN_NOTE1 (varchar(40))
      REMOVE cspOWN_NOTE2 (varchar(40))
      REMOVE cspPAR_ALTID (varchar(30))
      REMOVE cspPAR_ADRNO (real64)
      REMOVE cspPAR_ADRADD (varchar(6))
      REMOVE cspPAR_ADRPREDIR (varchar(2))
      REMOVE cspPAR_ADRSTR (varchar(30))
      REMOVE cspPAR_ADRSUF (varchar(8))
      REMOVE cspPAR_ADRPOSTDIR (varchar(5))
      REMOVE cspPAR_UNITDESC (varchar(10))
      REMOVE cspPAR_UNITNO (varchar(10))
      REMOVE cspNBHD (varchar(8))
      REMOVE cspCLASS (varchar(4))
      REMOVE cspLUC (varchar(4))
      REMOVE cspLIVUNIT (varchar(3))
      REMOVE cspZONING (varchar(8))
      REMOVE cspPAR_NOTE1 (varchar(40))
      REMOVE cspPAR_NOTE2 (varchar(40))
      REMOVE cspPAR_ZIP (varchar(5))
      REMOVE cspPAR_ADDR1 (varchar(80))
      REMOVE cspTPARCEL (varchar(30))
      REMOVE cspPAID (varchar(30))
      REMOVE cspLANDUSE (varchar(50))
      REMOVE cspMUNI (varchar(30))
      REMOVE cspLongitude (real64)
      REMOVE cspLatitude (real64)
      REMOVE cspTAXYR (int32)
      REMOVE cspShape_Length (real64)
      REMOVE cspShape_Area (real64)
    USER_EXPOSED_ATTRIBUTES = comments,effective,expire,extResrce,gcEditBy,gcException,gcLabel,gcModDate,gcModType,gcUnqID,OBJECTID,parAdd,parNum,parOwn,parOwn2,parOwnAdd,parOwnTel,parStreet,parType,Shape_Area,Shape_Length,srcLastEdt,srcOfData,srcUnqID,uploadAuth,uploadDate
    -> NullAttributeMapper
Note: Consider adding fme_db_operation operators in change detection for only loading changes in the future. MUST have a match id field that works and is properly mapped
NullAttributeMapper
    ATTRCHOICE_ACTION = SELECTED
    ATTRLIST = comments effective expire extResrce gcEditBy gcException gcLabel gcModDate gcModType gcUnqID OBJECTID parAdd parNum parOwn parOwn2 parOwnAdd parOwnTel parStreet parType srcLastEdt srcOfData uploadAuth uploadDate
    NULL_TREATMENT_LU = DELETEATTR
    OTHER_VALUE = " "
    REG_EXP = "  "
    SOURCE_ATTR_VAL_LU = SETNULL
    ATTRCHOICE = Selected Attributes
    NULL_TREATMENT = Missing
    SOURCE_ATTR_VAL = Null
    -> MapData/Parcels (writer GEODATABASE_FILE_6)
Note: Disabled per staff request
Parcel_Number_Cleaner: Parcel Number Cleaner [off]
    PARCELID = @Value(PARCELID)

Bookmark: Writer: Parcels (unchanged)
MapData/Parcels (writer GEODATABASE_FILE_6)
    attributes: srcUnqID char(20), comments char(100), effective date, expire date, extResrce char(254), gcEditBy char(100), gcException char(75), gcLabel char(150), gcModDate date, gcModType char(2), gcUnqID char(38), OBJECTID integer, parAdd char(150), parNum integer, parOwn char(150), parOwn2 char(150), parOwnAdd char(150), parOwnTel char(15), parStreet char(100), parType char(100), srcLastEdt date, srcOfData char(75), uploadAuth char(75), uploadDate date

Bookmark: Source ETL'd Parcels
MapData/Parcels (reader GEODATABASE_FILE_2)
    attributes: OBJECTID integer, gcUnqID char(38), srcOfData char(75), srcLastEdt date, uploadAuth char(75), uploadDate date, effective date, expire date, srcUnqID char(100), parOwn char(150), parOwn2 char(150), parOwnAdd char(150), parOwnTel char(15), parAdd char(150), parNum integer, parStreet char(100), parType char(100), extResrce char(254), comments char(100), gcModDate date, gcModType char(2), gcEditBy char(100), gcException char(75), gcLabel char(150), Shape_Length double, Shape_Area double
    -> Rename_Parcels
Rename_Parcels: BulkAttributeRenamer
    ATTRCHOICE_ACTION = NONPROTECTEDFME
    MODE_CHOICE = RENAME
    PATTERN_ACTION_DISP = ADDPREFIX
    REPLACE_STR = p
    ATTRCHOICE = All Attributes
    -> Prep_Source_Parcels

Bookmark: Source: Parcels Curated
MapData/Parcels_Curated (reader GEODATABASE_FILE_4)
    attributes: OBJECTID integer, SubdName char(200), Source char(75), EditDate date, UploadAuth char(75), UploadDate date, Effective date, Expire date, ParOwn char(150), ParOwn2 char(150), ParOwn3 char(150), ParOwnTel char(15), ParAddress char(150), ParStNum integer, ParStName char(100), ParStType char(100), ExtResrce char(254), Comments char(100), ParcelID char(100), Shape_Length double, Shape_Area double
    -> Junction_3

Bookmark: Writer: Parcels Curated
Parcels_Curated (writer GEODATABASE_FILE_3)
    attributes: OBJECTID integer, ParcelID char(38), SubdName char(200), Source char(75), EditDate date, UploadAuth char(75), UploadDate date, Effective date, Expire date, ParOwn char(150), ParOwn2 char(150), ParOwn3 char(150), ParOwnTel char(15), ParAddress char(150), ParStNum integer, ParStName char(100), ParStType char(100), ExtResrce char(254), Comments char(100)

FME custom transformer Subd Name Cleaners
Extracts info from the parcels info text files sent by the Assessor's Office

Parameters:
- TEXT_LINE_DATA = @Value(text_line_data)   # Text Line Data
- _SUBDNAME = @Value(_SubdName)   # Subdname
- FME_PROCESS_GROUP_BY =   # "" Group By
- FME_PROCESS_GROUPS_ORDERED = No   # When All Features Received,No%When Group Changes (Advanced),Yes Complete Groups

Note: Note: This tool uses all UPPER CASE characters. Change to upper case if needed.
Input (input)
    -> Clean_Init_Space
Note: Remove double, leading, and trailing spaces. Loop back to this if spaces are found at the end again
Note: Loop to here to run through scenarios again if needed
Note: Dashes need special logic because there are legitimate uses in names
Note: regex
Note: Clean up some strings for easier handling as well
Note: regex
Note: Replace text using regex based on specific senarios
start_of_scenarios (input)
    -> filter_legitimate_uses
Note: If initials appear to be legitimate (like in MLK Junior), and one or more of the initials was seen as a roman numeral & changed to a number, change it back to the respective letter.
Note: Look for double spaces again. If found, send to beginning, so the logic can be checked again
Note: Check all scenarios again to account for instances where more than one scenario was found in a string and the replacements changed the string formatting in the first pass (extra spaces, etc.)
Note: Remove duplicates from subdivision names. Using lists
check_all_scenarios_again: Tester
    BOOL_OP = OR
    TEST_CLAUSE:
      CASE_INSENSITIVE_TEST @Value(_SubdName) CONTAINS_REGEX \b((RE\s*(S<pipe>V<pipe>SUB<pipe>VISION<pipe>SUBDV<pipe>SUBDIVISION)?(S<pipe>V)?<pipe>ADD(N<pipe>ITION)?(S)?<pipe>P(ART<pipe>T)?(S)?<pipe>S\s*D<pipe>AMEND(MENT)?(S)?<pipe>(\sTH\s)?INT<pipe>N(ORTH)?<pipe>S(OUTH)?<pipe>W(WEST)?<pipe>E(AST)?<pipe>P(ART<pipe>T<pipe>AR)?(S)?<pipe>P\s*O<pipe>P\s*T)\s+(OF<pipe>TO<pipe>IN)).*<pipe>\b(?:\d{1,3}(?:ST<pipe>ND<pipe>RD<pipe>TH)\s*)?(?:PT<pipe>PART<pipe>RE(S)?(UB)?(DIVISION)?<pipe>REV(ISION)?<pipe>REFLECTIONS<pipe>SUB(D)?(V)?(ISION)?<pipe>SD<pipe>RE\s*SUB<pipe>PLAT<pipe>AMEND(MENT)?<pipe>ADD(N)<pipe>ADDITION<pipe>PLA(N)?<pipe>REV\s*PLAN)\s*(?:OF<pipe>TO)\s*(?:THE<pipe>TO)?<pipe>(OF\s*TO\s*(\d+)?)\b<pipe>\d{1,3}(?:ST<pipe>ND<pipe>RD<pipe>TH)$
      CASE_INSENSITIVE_TEST @Value(_SubdName) CONTAINS_REGEX \b(ZZZ<pipe>LT<pipe>LOT<pipe>BL(?:CK<pipe>K<pipe>OCK)<pipe>PH(?:ASE)?<pipe>AD(?:D<pipe>DITION<pipe>DN<pipe>DT)?<pipe>PARCEL<pipe>SEC(?:T<pipe>TION)?<pipe>TR(?:A<pipe>C<pipe>T)?<pipe>REV(?:ISION<pipe>ISED)?<pipe>COND(?:O<pipe>MINIUM)?<pipe>P(AR)?T<pipe>AREA<pipe>FINAL<pipe>FN(?:L)?<pipe>PL(?:A<pipe>N)?<pipe>AMEN(?:D<pipe>DMENT)?<pipe>TW(?:P)?<pipe>TOWNSHIP<pipe>OUTL(?:INE)?<pipe>NO<pipe>PD<pipe>CP<pipe>PB<pipe>PG)\s*([A-Z]{1}<pipe>\d+)\b<pipe>\b(?:\d+[A-Z]+<pipe>[A-Z]+\d+<pipe>\d+<pipe>[A-Z]{1})(\s*-\s*)(?:\d+[A-Z]+<pipe>[A-Z]+\d+<pipe>\d+<pipe>[A-Z]{1})\b<pipe>\b(?:\d+(ST<pipe>ND<pipe>RD<pipe>TH)\s*)?(ZZZ<pipe>LT<pipe>LOT<pipe>BL(?:CK<pipe>K<pipe>OCK)<pipe>PH(?:ASE)?<pipe>AD(?:D<pipe>DITION<pipe>DN<pipe>DT)?<pipe>PARCEL<pipe>SEC(?:T<pipe>TION)?<pipe>TR(?:A<pipe>C<pipe>T)?<pipe>REV(?:ISION<pipe>ISED)?<pipe>COND(?:O<pipe>MINIUM)?<pipe>P(AR)?T<pipe>AREA<pipe>FINAL<pipe>FN(?:L)?<pipe>PL(?:A<pipe>N)?<pipe>AMEN(?:D<pipe>DMENT)?<pipe>TW(?:P)?<pipe>TOWNSHIP<pipe>OUTL(?:INE)?<pipe>NO<pipe>PD<pipe>CP<pipe>PB<pipe>PG)(?:\s*\d+(ST<pipe>ND<pipe>RD<pipe>TH))?\b
      CASE_INSENSITIVE_TEST @Value(_SubdName) CONTAINS_REGEX ^(TO<pipe>AND<pipe>ABOUT<pipe>LIKE<pipe>ABOVE<pipe>NEAR<pipe>ACROSS<pipe>OF<pipe>AFTER<pipe>OFF<pipe>AGAINST<pipe>ON<pipe>ALONG<pipe>ONTO<pipe>AMONG<pipe>OPPOSITE<pipe>AROUND<pipe>OUT<pipe>AS<pipe>OUTSIDE<pipe>AT<pipe>OVER<pipe>BEFORE<pipe>PAST<pipe>BEHIND<pipe>ROUND<pipe>BELOW<pipe>SINCE<pipe>BENEATH<pipe>THAN<pipe>BESIDE<pipe>THROUGH<pipe>BETWEEN<pipe>TO<pipe>BEYOND<pipe>TOWARDS<pipe>BY<pipe>UNDER<pipe>DESPITE<pipe>UNDERNEATH<pipe>DOWN<pipe>UNLIKE<pipe>DURING<pipe>UNTIL<pipe>EXCEPT<pipe>UP<pipe>FOR<pipe>UPON<pipe>FROM<pipe>VIA<pipe>IN<pipe>WITH<pipe>INSIDE<pipe>WITHIN<pipe>INTO<pipe>WITHOUT)\b<pipe>\b(TO<pipe>AND<pipe>ABOUT<pipe>LIKE<pipe>ABOVE<pipe>NEAR<pipe>ACROSS<pipe>OF<pipe>AFTER<pipe>OFF<pipe>AGAINST<pipe>ON<pipe>ALONG<pipe>ONTO<pipe>AMONG<pipe>OPPOSITE<pipe>AROUND<pipe>OUT<pipe>AS<pipe>OUTSIDE<pipe>AT<pipe>OVER<pipe>BEFORE<pipe>PAST<pipe>BEHIND<pipe>ROUND<pipe>BELOW<pipe>SINCE<pipe>BENEATH<pipe>THAN<pipe>BESIDE<pipe>THROUGH<pipe>BETWEEN<pipe>TO<pipe>BEYOND<pipe>TOWARDS<pipe>BY<pipe>UNDER<pipe>DESPITE<pipe>UNDERNEATH<pipe>DOWN<pipe>UNLIKE<pipe>DURING<pipe>UNTIL<pipe>EXCEPT<pipe>UP<pipe>FOR<pipe>UPON<pipe>FROM<pipe>VIA<pipe>IN<pipe>WITH<pipe>INSIDE<pipe>WITHIN<pipe>INTO<pipe>WITHOUT<pipe>THE<pipe>MINOR)$
      CASE_INSENSITIVE_TEST @Value(_SubdName) CONTAINS_REGEX (?<=^<pipe>\b)(MINOR\s*)?(ADD(N)?<pipe>BL(O)?K<pipe>PH(\d+)?<pipe>RE(V)?<pipe>SEC<pipe>LOT<pipe>PAR<pipe>TWP<pipe>TR(A)?CT<pipe>AREA<pipe>PART<pipe>PT<pipe>(RE)?SUB(D<pipe>V)?(IVISION)?<pipe>SUBDV<pipe>SUB<pipe>RE\s*SUB<pipe>S\sD<pipe>AMEN(D)?(ED)?(\s*PLAN)?<pipe>AMEN(D)?(MENT)?<pipe>(RE<pipe>UN)?REC(ORDED)?<pipe>UNRE(ORDD)?<pipe>FINAL\s*PLA(N<pipe>T)?<pipe>OUTLINE\s*PLA(N<pipe>T)?<pipe>PLANNED<pipe>PROPOSED<pipe>P\s*D<pipe>SD<pipe>RES(TATED)?<pipe>(RE)?PLA(N<pipe>T<pipe>TTING)?(S)?<pipe>C\s*U\s*(P)?<pipe>P\s*U\s*(D<pipe>C)?<pipe>C\s*P<pipe>R\s*R<pipe>B\s*L<pipe>\s*&<pipe>\bMCC\b<pipe>(P\s*)?D(E)?(V)?(ELO)?P(MEN)?T)(?=\b<pipe>$)
      CASE_INSENSITIVE_TEST @Value(_SubdName) CONTAINS_REGEX ^\d+\b<pipe>\b\d+$<pipe>\b\d+\s*F(T<pipe>EET)?<pipe>\d+[A-Z]+<pipe>[A-Z]+\d+\b<pipe>\b(\d{1}<pipe>[A-Z]{1})\s*&\s*(\d{1}<pipe>[A-Z]{1})\b<pipe>\b\w{1}$
      CASE_INSENSITIVE_TEST @Value(_SubdName) CONTAINS_REGEX (?<=\s)(&<pipe>-<pipe>"<pipe>'<pipe>`<pipe>;<pipe>@<pipe>:<pipe>~<pipe>%)(?=\w)<pipe>(?<=\w)(&<pipe>-<pipe>"<pipe>'<pipe>`<pipe>;<pipe>@<pipe>:<pipe>~<pipe>%)(?=\s)<pipe>^(&<pipe>-<pipe>"<pipe>'<pipe>`<pipe>;<pipe>@<pipe>:<pipe>~<pipe>%)<pipe>(&<pipe>-<pipe>"<pipe>'<pipe>`<pipe>;<pipe>@<pipe>:<pipe>~<pipe>%)$
    TEST_MODE = CASE_INSENSITIVE_TEST
    PASSED -> start_of_scenarios (output)
    FAILED -> split_subd_name
Output (output)
Note: regex
Note: Send back to beginning to be checked again
start_of_scenarios (output)

Bookmark: Preemptively Remove Extra Spaces
Clean_Init_Space: StringReplacer
    CASE = NO
    NO_MATCH = _FME_NO_OP_
    REGEXP = NO
    STR_REPLACE_TABLE = "_SubdName     "
    -> filter_legitimate_uses

Bookmark: Dash Scenarios
filter_legitimate_uses: Tester
    BOOL_OP = COMPOSITE
    COMPOSITE_TEST = 1 OR 2 OR 3 AND 4
    TEST_CLAUSE:
      CASE_INSENSITIVE_TEST @Value(_SubdName) BEGINS_WITH -
      CASE_INSENSITIVE_TEST @Value(_SubdName) ENDS_WITH -
      CASE_INSENSITIVE_TEST @Value(_SubdName) CONTAINS_REGEX (?:^|\b\s)(\w{1,2}-\w{1,2}|\w{1,2}-|-\w{1,2})(?:$|\b|\s)
      CASE_INSENSITIVE_TEST @Value(_SubdName) NOT_CONTAINS_REGEX \b[A-Z]+-[A-Z]+\b|\b[A-Z]+\s-\s[A-Z]+\b
    TEST_MODE = CASE_INSENSITIVE_TEST
    PASSED -> dash_begin_or_end
    FAILED -> Junction
dash_begin_or_end: StringReplacer
    CASE = NO
    NO_MATCH = _FME_NO_OP_
    REGEXP = NO
    STR_REPLACE_TABLE = "_SubdName -  "
    -> Junction
Junction
    -> and_to_amp

Bookmark: Preemptive cleanup of strings
and_to_amp: StringReplacer
    CASE = NO
    NO_MATCH = _FME_NO_OP_
    REGEXP = YES
    STR_REPLACE_TABLE = _SubdName \bAND\b &
    -> re_1st_pass

Bookmark: Primary regex scenarios
Note: Descriptive phrases
Note: Examples: / "RESUBDIVISION OF" in RESUBDIVISION OF LOT 10" / "PART OF" in "PART OF BLOCK A" / "2ND AMENDMENT TO" in "2ND AMENDMENT TO THE PLAT" / "5TH REVISED PLAN OF" in "5TH REVISED PLAN OF THE ESTATES"
re_1st_pass: StringReplacer
    CASE = NO
    NO_MATCH = _FME_NO_OP_
    REGEXP = YES
    STR_REPLACE_TABLE = _SubdName \b((RE\s*(S<pipe>V<pipe>SUB<pipe>VISION<pipe>SUBDV<pipe>SUBDIVISION)?(S<pipe>V)?<pipe>ADD(N<pipe>ITION)?(S)?<pipe>P(ART<pipe>T)?(S)?<pipe>S\s*D<pipe>AMEND(MENT)?(S)?<pipe>(\sTH\s)?INT<pipe>N(ORTH)?<pipe>S(OUTH)?<pipe>W(WEST)?<pipe>E(AST)?<pipe>P(ART<pipe>T<pipe>AR)?(S)?<pipe>P\s*O<pipe>P\s*T)\s+(OF<pipe>TO<pipe>IN)).*<pipe>\b(?:\d{1,3}(?:ST<pipe>ND<pipe>RD<pipe>TH)\s*)?(?:PT<pipe>PART<pipe>RE(S)?(UB)?(DIVISION)?<pipe>REV(ISION)?<pipe>REFLECTIONS<pipe>SUB(D)?(V)?(ISION)?<pipe>SD<pipe>RE\s*SUB<pipe>PLAT<pipe>AMEND(MENT)?<pipe>ADD(N)<pipe>ADDITION<pipe>PLA(N)?<pipe>REV\s*PLAN)\s*(?:OF<pipe>TO)\s*(?:THE<pipe>TO)?<pipe>(OF\s*TO\s*(\d+)?)\b<pipe>\d{1,3}(?:ST<pipe>ND<pipe>RD<pipe>TH)$
    -> re_2nd_pass
Note: Keyword alphanumeric combinations
Note: Examples: / "ZZZ 5" in "ZZZ 5 BLOCK 1" / "A - 10" in "BLOCK 2 SECTION A - 10" / "2ND ZZZ" in "2ND ZZZ PART A" / "SEC B2" in " CARROLLWOOD LAKES SEC B2" / "PH 2A" in " EMERALD ESTATES PH 2A "
re_2nd_pass: StringReplacer
    CASE = NO
    NO_MATCH = _FME_NO_OP_
    REGEXP = YES
    STR_REPLACE_TABLE = _SubdName \b(ZZZ<pipe>LT<pipe>LOT<pipe>BL(?:CK<pipe>K<pipe>OCK)<pipe>PH(?:ASE)?<pipe>AD(?:D<pipe>DITION<pipe>DN<pipe>DT)?<pipe>PARCEL<pipe>SEC(?:T<pipe>TION)?<pipe>TR(?:A<pipe>C<pipe>T)?<pipe>REV(?:ISION<pipe>ISED)?<pipe>COND(?:O<pipe>MINIUM)?<pipe>P(AR)?T<pipe>AREA<pipe>FINAL<pipe>FN(?:L)?<pipe>PL(?:A<pipe>N)?<pipe>AMEN(?:D<pipe>DMENT)?<pipe>TW(?:P)?<pipe>TOWNSHIP<pipe>OUTL(?:INE)?<pipe>NO<pipe>PD<pipe>CP<pipe>PB<pipe>PG)\s*([A-Z]{1}<pipe>\d+)\b<pipe>\b(?:\d+[A-Z]+<pipe>[A-Z]+\d+<pipe>\d+<pipe>[A-Z]{1})(\s*-\s*)(?:\d+[A-Z]+<pipe>[A-Z]+\d+<pipe>\d+<pipe>[A-Z]{1})\b<pipe>\b(?:\d+(ST<pipe>ND<pipe>RD<pipe>TH)\s*)?(ZZZ<pipe>LT<pipe>LOT<pipe>BL(?:CK<pipe>K<pipe>OCK)<pipe>PH(?:ASE)?<pipe>AD(?:D<pipe>DITION<pipe>DN<pipe>DT)?<pipe>PARCEL<pipe>SEC(?:T<pipe>TION)?<pipe>TR(?:A<pipe>C<pipe>T)?<pipe>REV(?:ISION<pipe>ISED)?<pipe>COND(?:O<pipe>MINIUM)?<pipe>P(AR)?T<pipe>AREA<pipe>FINAL<pipe>FN(?:L)?<pipe>PL(?:A<pipe>N)?<pipe>AMEN(?:D<pipe>DMENT)?<pipe>TW(?:P)?<pipe>TOWNSHIP<pipe>OUTL(?:INE)?<pipe>NO<pipe>PD<pipe>CP<pipe>PB<pipe>PG)(?:\s*\d+(ST<pipe>ND<pipe>RD<pipe>TH))?\b
    -> re_3rd_pass
Note: Specific articles and prepositions at the beginning or end
Note: Examples: / "THE" in " WOODLANDS OF CORDOVA PD THE" / "BETWEEN" in "PAR 1 BETWEEN BLOCK 1 AND 2
re_3rd_pass: StringReplacer
    CASE = NO
    NO_MATCH = _FME_NO_OP_
    REGEXP = YES
    STR_REPLACE_TABLE = _SubdName ^(TO<pipe>AND<pipe>ABOUT<pipe>LIKE<pipe>ABOVE<pipe>NEAR<pipe>ACROSS<pipe>OF<pipe>AFTER<pipe>OFF<pipe>AGAINST<pipe>ON<pipe>ALONG<pipe>ONTO<pipe>AMONG<pipe>OPPOSITE<pipe>AROUND<pipe>OUT<pipe>AS<pipe>OUTSIDE<pipe>AT<pipe>OVER<pipe>BEFORE<pipe>PAST<pipe>BEHIND<pipe>ROUND<pipe>BELOW<pipe>SINCE<pipe>BENEATH<pipe>THAN<pipe>BESIDE<pipe>THROUGH<pipe>BETWEEN<pipe>TO<pipe>BEYOND<pipe>TOWARDS<pipe>BY<pipe>UNDER<pipe>DESPITE<pipe>UNDERNEATH<pipe>DOWN<pipe>UNLIKE<pipe>DURING<pipe>UNTIL<pipe>EXCEPT<pipe>UP<pipe>FOR<pipe>UPON<pipe>FROM<pipe>VIA<pipe>IN<pipe>WITH<pipe>INSIDE<pipe>WITHIN<pipe>INTO<pipe>WITHOUT)\b<pipe>\b(TO<pipe>AND<pipe>ABOUT<pipe>LIKE<pipe>ABOVE<pipe>NEAR<pipe>ACROSS<pipe>OF<pipe>AFTER<pipe>OFF<pipe>AGAINST<pipe>ON<pipe>ALONG<pipe>ONTO<pipe>AMONG<pipe>OPPOSITE<pipe>AROUND<pipe>OUT<pipe>AS<pipe>OUTSIDE<pipe>AT<pipe>OVER<pipe>BEFORE<pipe>PAST<pipe>BEHIND<pipe>ROUND<pipe>BELOW<pipe>SINCE<pipe>BENEATH<pipe>THAN<pipe>BESIDE<pipe>THROUGH<pipe>BETWEEN<pipe>TO<pipe>BEYOND<pipe>TOWARDS<pipe>BY<pipe>UNDER<pipe>DESPITE<pipe>UNDERNEATH<pipe>DOWN<pipe>UNLIKE<pipe>DURING<pipe>UNTIL<pipe>EXCEPT<pipe>UP<pipe>FOR<pipe>UPON<pipe>FROM<pipe>VIA<pipe>IN<pipe>WITH<pipe>INSIDE<pipe>WITHIN<pipe>INTO<pipe>WITHOUT<pipe>THE<pipe>MINOR)$
    -> re_4th_pass
Note: Standalone keyphrases
Note: Examples: / "ADDN" in "HARTS EVERGREEN ADDN BLK A UNREC" / "BLOCK" in "EAST END PLACE BLOCK" / "P U D" in "TARA WOODS P U D"
re_4th_pass: StringReplacer
    CASE = NO
    NO_MATCH = _FME_NO_OP_
    REGEXP = YES
    STR_REPLACE_TABLE = _SubdName (?<=^<pipe>\b)(MINOR\s*)?(ADD(N)?<pipe>BL(O)?K<pipe>PH(\d+)?<pipe>RE(V)?<pipe>SEC<pipe>LOT<pipe>PAR<pipe>TWP<pipe>TR(A)?CT<pipe>AREA<pipe>PART<pipe>PT<pipe>(RE)?SUB(D<pipe>V)?(IVISION)?<pipe>SUBDV<pipe>SUB<pipe>RE\s*SUB<pipe>S\sD<pipe>AMEN(D)?(ED)?(\s*PLAN)?<pipe>AMEN(D)?(MENT)?<pipe>(RE<pipe>UN)?REC(ORDED)?<pipe>UNRE(ORDD)?<pipe>FINAL\s*PLA(N<pipe>T)?<pipe>OUTLINE\s*PLA(N<pipe>T)?<pipe>PLANNED<pipe>PROPOSED<pipe>P\s*D<pipe>SD<pipe>RES(TATED)?<pipe>(RE)?PLA(N<pipe>T<pipe>TTING)?(S)?<pipe>C\s*U\s*(P)?<pipe>P\s*U\s*(D<pipe>C)?<pipe>C\s*P<pipe>R\s*R<pipe>B\s*L<pipe>\s*&<pipe>\bMCC\b<pipe>(P\s*)?D(E)?(V)?(ELO)?P(MEN)?T)(?=\b<pipe>$)
    -> re_5th_pass
Note: Standalone numbers / (including units)
Note: Examples: / "1" in "ROCKYFORD 1" / "2" in "OAKS AT APPLING 2 PD"
re_5th_pass: StringReplacer
    CASE = NO
    NO_MATCH = _FME_NO_OP_
    REGEXP = YES
    STR_REPLACE_TABLE = _SubdName ^\d+\b<pipe>\b\d+$<pipe>\b\d+\s*F(T<pipe>EET)?<pipe>\d+[A-Z]+<pipe>[A-Z]+\d+\b<pipe>\b(\d{1}<pipe>[A-Z]{1})\s*&\s*(\d{1}<pipe>[A-Z]{1})\b<pipe>\b\w{1}$
    -> re_6th_pass
Note: Remant spec characters
Note: Examples: / "&" in "FOUNTAIN BROOK &" / "&" in "SHELTON HINSON TRACT& WAG"
re_6th_pass: StringReplacer
    CASE = NO
    NO_MATCH = _FME_NO_OP_
    REGEXP = YES
    STR_REPLACE_TABLE = _SubdName (?<=\s)(&<pipe>-<pipe>"<pipe>'<pipe>`<pipe>;<pipe>@<pipe>:<pipe>~<pipe>%)(?=\w)<pipe>(?<=\w)(&<pipe>-<pipe>"<pipe>'<pipe>`<pipe>;<pipe>@<pipe>:<pipe>~<pipe>%)(?=\s)<pipe>^(&<pipe>-<pipe>"<pipe>'<pipe>`<pipe>;<pipe>@<pipe>:<pipe>~<pipe>%)<pipe>(&<pipe>-<pipe>"<pipe>'<pipe>`<pipe>;<pipe>@<pipe>:<pipe>~<pipe>%)$
    -> if_legitimate_initials

Bookmark: Deal with initials
if_legitimate_initials: Tester
    BOOL_OP = OR
    TEST_CLAUSE = CASE_SENSITIVE_TEST @Value(_SubdName) CONTAINS_REGEX \b([A-Z]{1}|1|5|10)\s(1|5|10)\b|\b(1|5|10)\s([A-Z]{1}|1|5|10)\b
    TEST_MODE = CASE_SENSITIVE_TEST
    PASSED -> filter_by_specific_init
    FAILED -> Junction_2
filter_by_specific_init: TestFilter
    DEFAULT_VALUE = <UNFILTERED>
    PASSED_TEST_GROUP_OUTPUT = FIRST
    TEST_LIST = "BOOL_OP,OR,COMPOSITE_TEST,""""""1"""""",TEST_CLAUSE,CASE_SENSITIVE_TEST @Value(_SubdName) CONTAINS_REGEX \b1\b",I - 1,"BOOL_OP,OR,COMPOSITE_TEST,""""""1"""""",TEST_CLAUSE,CASE_SENSITIVE_TEST @Value(_SubdName) CONTAINS_REGEX \b5\b",V - 5,"BOOL_OP,OR,COMPOSITE_TEST,""""""1"""""",TEST_CLAUSE,CASE_SENSITIVE_TEST @Value(_SubdName) CONTAINS_REGEX \b10\b",X - 10
    I - 1 -> from_1_to_I
    V - 5 -> from_5_to_V
    X - 10 -> from_10_to_X
    <UNFILTERED> -> Junction_2
from_1_to_I: StringReplacer
    CASE = NO
    NO_MATCH = _FME_NO_OP_
    REGEXP = YES
    STR_REPLACE_TABLE = _SubdName \b1\b I
    -> Junction_2
from_5_to_V: StringReplacer
    CASE = NO
    NO_MATCH = _FME_NO_OP_
    REGEXP = YES
    STR_REPLACE_TABLE = _SubdName \b5\b V
    -> Junction_2
from_10_to_X: StringReplacer
    CASE = NO
    NO_MATCH = _FME_NO_OP_
    REGEXP = YES
    STR_REPLACE_TABLE = _SubdName \b10\b X
    -> Junction_2
Junction_2
    -> Tim_at_ends

Bookmark: Check for spaces again
Tim_at_ends: AttributeTrimmer
    SRC_ATTRS = _SubdName
    TRIM_CHARS = " "
    TRIM_TO_NONE = No
    TRIM_TYPE = BOTH
    -> replace_internal_sp
replace_internal_sp: StringReplacer
    CASE = NO
    NO_MATCH = _FME_NO_OP_
    REGEXP = YES
    STR_REPLACE_TABLE = "_SubdName     "
    -> check_all_scenarios_again

Bookmark: Remove duplicates
split_subd_name: AttributeSplitter
    ATTR_NAME = _SubdName
    DELIMITER = " "
    DROP_EMPTY_PARTS = YES
    LIST_NAME = _SubName_Split_List
    TRIM_TYPE = BOTH
    -> remove_list_dups
remove_list_dups: ListDuplicateRemover
    SRC_LIST = _SubName_Split_List{}
    -> put_name_back_together
put_name_back_together: ListConcatenator
    DROP_EMPTY_PARTS = No
    LIST_ATTR = _SubName_Split_List{}
    SEP = " "
    VAL_ATTR = _SubdName
    -> Output (output)

FME custom transformer Title Case

Parameters:
- _SUBDNAME = @Value(_SubdName)   # Subdname
- FME_PROCESS_GROUP_BY =   # "" Group By
- FME_PROCESS_GROUPS_ORDERED = No   # When All Features Received,No%When Group Changes (Advanced),Yes Complete Groups

Input (input)
    -> Change_to_Title
Note: Change _SubdName to Full Title Case
Change_to_Title: StringCaseChanger
    ATTRCHOICE = SELECTED
    ATTRLIST = _SubdName
    CHANGE_TYPE = fulltitle
    -> Find_MC
Note: Note: this is not by any means an exhaustive list of exceptions. Add more as needed
Output (output)

Bookmark: Mc Scenarios
Note: Do a regex search for MC[A-Z] to find examples like McFarlin
Note: If not found, continue...
Find_MC: Tester
    BOOL_OP = OR
    TEST_CLAUSE = CASE_INSENSITIVE_TEST @Value(_SubdName) CONTAINS_REGEX MC[A-Z]
    TEST_MODE = CASE_INSENSITIVE_TEST
    PASSED -> Replace_Mc
    FAILED -> Junction
Note: Replace Mc with ~~~ / This is done because those characters are guaranteed to not be used legitimately in the data. This way we can find these later and replace them with Mc again
Replace_Mc: StringReplacer
    CASE = NO
    NO_MATCH = _FME_NO_OP_
    REGEXP = NO
    STR_REPLACE_TABLE = _SubdName Mc ~~~
    -> Split_Title_Case
Note: Change to newly split strings to title case
Split_Title_Case: StringCaseChanger
    ATTRCHOICE = SELECTED
    ATTRLIST = _SubdName
    CHANGE_TYPE = fulltitle
    -> Replace_wth_Mc
Note: Replace ~~~ with Mc again
Replace_wth_Mc: StringReplacer
    CASE = NO
    NO_MATCH = _FME_NO_OP_
    REGEXP = NO
    STR_REPLACE_TABLE = _SubdName ~~~ Mc
    -> MixedCase_Exceptions
Junction
    -> MixedCase_Exceptions

Bookmark: Notable Exceptions
Note: Search for each individually
MixedCase_Exceptions: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_SubdName) CONTAINS_REGEX YMCA",YMCA,"BOOL_OP,OR,COMPOSITE_TEST,""""""1"""""",TEST_CLAUSE,CASE_INSENSITIVE_TEST @Value(_SubdName) CONTAINS_REGEX (^USA | USA | USA$)",USA,"BOOL_OP,OR,COMPOSITE_TEST,""""""1"""""",TEST_CLAUSE,CASE_INSENSITIVE_TEST @Value(_SubdName) CONTAINS_REGEX (^TN <pipe> TN <pipe> TN$)",TN,"BOOL_OP,OR,COMPOSITE_TEST,""""""1"""""",TEST_CLAUSE,CASE_INSENSITIVE_TEST @Value(_SubdName) CONTAINS_REGEX \sOF\s",Of
    YMCA -> YMCA
    USA -> USA
    TN -> TN
    Of -> Of
    <UNFILTERED> -> Output (output)
Note: Then replace with the exception
YMCA: StringReplacer
    CASE = NO
    NO_MATCH = _FME_NO_OP_
    REGEXP = YES
    STR_REPLACE_TABLE = _SubdName YMCA YMCA
    -> Junction_2
USA: StringReplacer
    CASE = NO
    NO_MATCH = _FME_NO_OP_
    REGEXP = YES
    STR_REPLACE_TABLE = _SubdName (^USA <pipe> USA <pipe> USA$) USA
    -> Junction_2
TN: StringReplacer
    CASE = NO
    NO_MATCH = _FME_NO_OP_
    REGEXP = YES
    STR_REPLACE_TABLE = _SubdName (^TN <pipe> TN <pipe> TN$) TN
    -> Junction_2
Of: StringReplacer
    CASE = NO
    NO_MATCH = _FME_NO_OP_
    REGEXP = YES
    STR_REPLACE_TABLE = "_SubdName \\sOF\\s  of "
    -> Junction_2
Junction_2
    -> Output (output)

FME custom transformer Prep Source Parcels

Parameters:
- PCOMMENTS = @Value(pcomments)   # pcomments
- PEFFECTIVE = @Value(peffective)   # peffective
- PEXPIRE = @Value(pexpire)   # pexpire
- PEXTRESRCE = @Value(pextResrce)   # pextResrce
- PGCEDITBY = @Value(pgcEditBy)   # pgcEditBy
- PGCEXCEPTION = @Value(pgcException)   # pgcException
- PGCLABEL = @Value(pgcLabel)   # pgcLabel
- PGCMODDATE = @Value(pgcModDate)   # pgcModDate
- PGCMODTYPE = @Value(pgcModType)   # pgcModType
- PGCUNQID = @Value(pgcUnqID)   # pgcUnqID
- POBJECTID = @Value(pOBJECTID)   # pOBJECTID
- PPARADD = @Value(pparAdd)   # pparAdd
- PPARNUM = @Value(pparNum)   # pparNum
- PPAROWN = @Value(pparOwn)   # pparOwn
- PPAROWN2 = @Value(pparOwn2)   # pparOwn2
- PPAROWNADD = @Value(pparOwnAdd)   # pparOwnAdd
- PPAROWNTEL = @Value(pparOwnTel)   # pparOwnTel
- PPARSTREET = @Value(pparStreet)   # pparStreet
- PPARTYPE = @Value(pparType)   # pparType
- PSHAPE_AREA = @Value(pShape_Area)   # Pshape Area
- PSHAPE_LENGTH = @Value(pShape_Length)   # Pshape Length
- PSRCLASTEDT = @Value(psrcLastEdt)   # psrcLastEdt
- PSRCOFDATA = @Value(psrcOfData)   # psrcOfData
- PSRCUNQID = @Value(psrcUnqID)   # psrcUnqID
- PUPLOADAUTH = @Value(puploadAuth)   # puploadAuth
- PUPLOADDATE = @Value(puploadDate)   # puploadDate

Input (input)
    -> Replace_Double_Spaces
    -> trim_ends_only
Note: Alternative that only removes leading and trailing spaces. Temporary and local fix to leave internal spaces per staff request
trim_ends_only: AttributeTrimmer
    SRC_ATTRS = psrcUnqID
    TRIM_CHARS = " "
    TRIM_TO_NONE = Yes
    TRIM_TYPE = BOTH
    -> Junction
Junction
    -> Output (output)
Spaces_Loop (input)
    -> Replace_Double_Spaces [off]
Note: Reduce double spaces to single spaces
Replace_Double_Spaces: StringReplacer [off]
    CASE = NO
    NO_MATCH = _FME_NO_OP_
    REGEXP = YES
    STR_REPLACE_TABLE = "psrcUnqID \\s{2,}  "
    -> trim_ends [off]
Note: Trim ends
trim_ends: StringReplacer [off]
    CASE = NO
    NO_MATCH = _FME_NO_OP_
    REGEXP = YES
    STR_REPLACE_TABLE = "psrcUnqID \\s$<pipe>^\\s "
    -> Check_Spaces_Again [off]
Note: Check to see if any other spaces were found. / Send back if found. Else continue...
Check_Spaces_Again: Tester [off]
    BOOL_OP = OR
    TEST_CLAUSE = CASE_SENSITIVE_TEST @Value(psrcUnqID) CONTAINS_REGEX \s{2,}<pipe>\s$<pipe>^\s
    TEST_MODE = CASE_SENSITIVE_TEST
    PASSED -> Spaces_Loop (output) [off]
    FAILED -> Output (output)
Output (output)
Spaces_Loop (output)

FME custom transformer Parcel Number Cleaner
Remove double spaces from parcels (and any other needed enhancements)

Parameters:
- PARCELID = @Value(PARCELID)

Input (input)
    -> replace_with_sngl_spc
Note: Send back if a double space is found again
Loop_to_string_replacement (input)
    -> replace_with_sngl_spc
replace_with_sngl_spc: StringReplacer
    CASE = NO
    FIND_TEXT = (  )+
    NO_MATCH = _FME_NO_OP_
    REGEXP = YES
    REPLACE_TEXT = " "
    SRC_ATTRS = PARCELID
    TEST_STRING = Enter a string to test here...
    -> find_dbl_spaces
find_dbl_spaces: Tester
    BOOL_OP = OR
    TEST_CLAUSE = CASE_SENSITIVE_TEST @Value(PARCELID) CONTAINS_REGEX (  )+
    TEST_MODE = TEST
    PASSED -> Loop_to_string_replacement (output)
    FAILED -> Output (output)
Loop_to_string_replacement (output)
Output (output)

FME custom transformer Clean up ParcelID

Parameters:
- _PARCELID = @Value(_ParcelID)   # Parcelid

Input (input)
    -> Replace_Double_Spaces
    -> trim_ends_only
Note: Alternative that only removes leading and trailing spaces. Temporary and local fix to leave internal spaces per staff request
trim_ends_only: AttributeTrimmer
    SRC_ATTRS = _ParcelID
    TRIM_CHARS = " "
    TRIM_TO_NONE = Yes
    TRIM_TYPE = BOTH
    -> Junction
Junction
    -> Output (output)
Spaces_Loop (input)
    -> Replace_Double_Spaces
Note: Reduce double spaces to single spaces
Replace_Double_Spaces: StringReplacer [off]
    CASE = NO
    NO_MATCH = _FME_NO_OP_
    REGEXP = YES
    STR_REPLACE_TABLE = "_ParcelID \\s{2,}  "
    -> trim_ends [off]
Note: Trim ends
trim_ends: StringReplacer [off]
    CASE = NO
    NO_MATCH = _FME_NO_OP_
    REGEXP = YES
    STR_REPLACE_TABLE = "_ParcelID \\s$<pipe>^\\s "
    -> Check_Spaces_Again [off]
Note: Check to see if any other spaces were found. / Send back if found. Else continue...
Check_Spaces_Again: Tester [off]
    BOOL_OP = OR
    TEST_CLAUSE = CASE_SENSITIVE_TEST @Value(_ParcelID) CONTAINS_REGEX \s{2,}<pipe>\s$<pipe>^\s
    TEST_MODE = CASE_SENSITIVE_TEST
    PASSED -> Spaces_Loop (output) [off]
    FAILED -> Output (output)
Output (output)
Spaces_Loop (output)

FME custom transformer Subd Name Replacement

Parameters:
- TEXT_LINE_DATA = @Value(text_line_data)   # Text Line Data
- FME_PROCESS_GROUP_BY =   # "" Group By
- FME_PROCESS_GROUPS_ORDERED = No   # When All Features Received,No%When Group Changes (Advanced),Yes Complete Groups

Note: First split attributes by comma, then map to a permanent field (take it out of a list), and then remove the "" from said field
Note: The following characters can't be matched literally in regex queries because they are part of the syntax and can't be matched individually through regex. These need to be replaced using regular text queries: .\/[]() / The following characters are also part of the syntax but they *can* be matched individually. These are OK to replace here through regex: {},:;
Note: NOTE: An exemption is dashes. Many of those are legitimate and can't be wholesale replaced here without some special logic. That logic is handled later
Note: Change spelled out ordinals to the / numeric versions for easier handling later
Note: Examples: / 3RD -----> 3RD / FOURTH -----> 4TH
Input (input)
    -> Split_by_QCommaQ
Note: Examples: / 1 ST ----> 1ST / 5 TH ----> 5TH
Note: Then remove spelled out numbers if they're accompanied by known descriptors like "Phase," "Block," etc. ZZZ is used as a string to be removed later
Note: Examples: / PHASE ONE ----> ZZZ / FOUR SEC ----> ZZZ
Note: Do the same for specific single-letter abbreviations like P U D that could cause issues with the logic downstream
Note: Replace roman numerals with their numeric equivalents
Note: Example: the "II" in Phase II A"
Junction_32
    -> Re-check_spec_chtrs
Re-check_spec_chtrs: Tester
    BOOL_OP = OR
    TEST_CLAUSE:
      CASE_INSENSITIVE_TEST @Value(_SubdName) CONTAINS_REGEX ("|#|`|;|@|:|~)
      CASE_INSENSITIVE_TEST @Value(_SubdName) CONTAINS_REGEX (["'])([A-Z\d]+-?[A-Z\d]+)\1|'\d+'|"\d+"
      CASE_INSENSITIVE_TEST @Value(_SubdName) CONTAINS (
      CASE_INSENSITIVE_TEST @Value(_SubdName) CONTAINS )
      CASE_INSENSITIVE_TEST @Value(_SubdName) CONTAINS .
      CASE_INSENSITIVE_TEST @Value(_SubdName) CONTAINS \
    TEST_MODE = CASE_INSENSITIVE_TEST
    PASSED -> Spec_Character_Loop (output)
    FAILED -> Output (output)
Output (output)
Spec_Character_Loop (output)

Bookmark: Prep fields
Split_by_QCommaQ: AttributeSplitter
    ATTR_NAME = text_line_data
    DELIMITER = ,
    DROP_EMPTY_PARTS = NO
    LIST_NAME = _ParcelInfo
    TRIM_TYPE = BOTH
    -> County_Total_Elements
County_Total_Elements: ListElementCounter
    CNT_ATTR = _element_count
    LIST_NAME = _ParcelInfo{}
    -> Filter_Out_Erratic
Note: If the number of elements is standard (12), continue. Else, send through the uncommon counts section below
Filter_Out_Erratic: Tester
    BOOL_OP = OR
    TEST_CLAUSE = NUM_TEST @Value(_element_count) = 12
    TEST_MODE = NUM_TEST
    PASSED -> element_12
    FAILED -> Uncommon_counts
element_12: AttributeCreator
    ATTR_TABLE:
      SET_TO _SubdName (varchar(200)) = @Value(_ParcelInfo{10})
      SET_TO _ParcelID (varchar(200)) = @Value(_ParcelInfo{0})
    INPUT_PORT_CONNECTED = CONNECTED
    -> Junction_2
Uncommon_counts: TestFilter
    DEFAULT_VALUE = <UNFILTERED>
    PASSED_TEST_GROUP_OUTPUT = FIRST
    TEST_LIST = "BOOL_OP,OR,COMPOSITE_TEST,""""""1"""""",TEST_CLAUSE,TEST @Value(_element_count) = 13",13,"BOOL_OP,OR,COMPOSITE_TEST,""""""1"""""",TEST_CLAUSE,TEST @Value(_element_count) = 14",14,"BOOL_OP,OR,COMPOSITE_TEST,""""""1"""""",TEST_CLAUSE,TEST @Value(_element_count) = 15",15,"BOOL_OP,OR,COMPOSITE_TEST,""""""1"""""",TEST_CLAUSE,TEST @Value(_element_count) = 16",16,"BOOL_OP,OR,COMPOSITE_TEST,""""""1"""""",TEST_CLAUSE,TEST @Value(_element_count) = 17",17,"BOOL_OP,OR,COMPOSITE_TEST,""""""1"""""",TEST_CLAUSE,TEST @Value(_element_count) = 18",18,"BOOL_OP,OR,COMPOSITE_TEST,""""""1"""""",TEST_CLAUSE,TEST @Value(_element_count) = 19",19,"BOOL_OP,OR,COMPOSITE_TEST,""""""1"""""",TEST_CLAUSE,TEST @Value(_element_count) = 20",20,"BOOL_OP,OR,COMPOSITE_TEST,""""""1"""""",TEST_CLAUSE,TEST @Value(_element_count) = 21",21
    13 -> element_13
    14 -> element_14
    15 -> element_15
    16 -> element_16
    17 -> element_17
    18 -> element_18
    19 -> element_19
    20 -> element_20
    21 -> element_21
    <UNFILTERED> -> Terminator
element_13: AttributeCreator
    ATTR_TABLE:
      SET_TO _SubdName (varchar(200)) = @Value(_ParcelInfo{11})
      SET_TO _ParcelID (varchar(200)) = @Value(_ParcelInfo{0})
    INPUT_PORT_CONNECTED = CONNECTED
    -> Junction
element_18: AttributeCreator
    ATTR_TABLE:
      SET_TO _SubdName (varchar(200)) = @Value(_ParcelInfo{16})
      SET_TO _ParcelID (varchar(200)) = @Value(_ParcelInfo{0})
    INPUT_PORT_CONNECTED = CONNECTED
    -> Junction
element_14: AttributeCreator
    ATTR_TABLE:
      SET_TO _SubdName (varchar(200)) = @Value(_ParcelInfo{12})
      SET_TO _ParcelID (varchar(200)) = @Value(_ParcelInfo{0})
    INPUT_PORT_CONNECTED = CONNECTED
    -> Junction
element_19: AttributeCreator
    ATTR_TABLE:
      SET_TO _SubdName (varchar(200)) = @Value(_ParcelInfo{17})
      SET_TO _ParcelID (varchar(200)) = @Value(_ParcelInfo{0})
    INPUT_PORT_CONNECTED = CONNECTED
    -> Junction
element_15: AttributeCreator
    ATTR_TABLE:
      SET_TO _SubdName (varchar(200)) = @Value(_ParcelInfo{13})
      SET_TO _ParcelID (varchar(200)) = @Value(_ParcelInfo{0})
    INPUT_PORT_CONNECTED = CONNECTED
    -> Junction
element_20: AttributeCreator
    ATTR_TABLE:
      SET_TO _SubdName (varchar(200)) = @Value(_ParcelInfo{18})
      SET_TO _ParcelID (varchar(200)) = @Value(_ParcelInfo{0})
    INPUT_PORT_CONNECTED = CONNECTED
    -> Junction
element_16: AttributeCreator
    ATTR_TABLE:
      SET_TO _SubdName (varchar(200)) = @Value(_ParcelInfo{14})
      SET_TO _ParcelID (varchar(200)) = @Value(_ParcelInfo{0})
    INPUT_PORT_CONNECTED = CONNECTED
    -> Junction
element_21: AttributeCreator
    ATTR_TABLE:
      SET_TO _SubdName (varchar(200)) = @Value(_ParcelInfo{21})
      SET_TO _ParcelID (varchar(200)) = @Value(_ParcelInfo{0})
    INPUT_PORT_CONNECTED = CONNECTED
    -> Junction
Note: This initial parsing is critical. Make sure that all scenarios are accounted for. Stop the tool with an error message otherwise
Terminator
    MESSAGE = Translation Terminated: unaccounted for element count found in Subd Name Replacement test filter
element_17: AttributeCreator
    ATTR_TABLE:
      SET_TO _SubdName (varchar(200)) = @Value(_ParcelInfo{15})
      SET_TO _ParcelID (varchar(200)) = @Value(_ParcelInfo{0})
    INPUT_PORT_CONNECTED = CONNECTED
    -> Junction
Junction
    -> Junction_2

Bookmark: Remove Spec Characters
Junction_2
    -> Remove_Apostrophes
Spec_Character_Loop (input)
    -> Remove_Apostrophes
Note: Special logic needed for ' because there are legitimate cases of their use
Remove_Apostrophes: StringReplacer
    CASE = NO
    NO_MATCH = _FME_NO_OP_
    REGEXP = YES
    STR_REPLACE_TABLE = _SubdName (["'])([A-Z\d]+-?[A-Z\d]+)\1<pipe>'\d+'<pipe>"\d+"
    -> Remove_Spec_Characters
Remove_Spec_Characters: StringReplacer
    CASE = NO
    NO_MATCH = _FME_NO_OP_
    REGEXP = YES
    STR_REPLACE_TABLE = _SubdName,_ParcelID ("<pipe>#<pipe>`<pipe>;<pipe>@<pipe>:<pipe>~<pipe>%)
    -> Replace_Parenthesis
Replace_Parenthesis: StringReplacer
    CASE = NO
    NO_MATCH = _FME_NO_OP_
    REGEXP = NO
    STR_REPLACE_TABLE = "_SubdName (  "
    -> Replace_Parenthesis_2
Replace_Parenthesis_2: StringReplacer
    CASE = NO
    NO_MATCH = _FME_NO_OP_
    REGEXP = NO
    STR_REPLACE_TABLE = "_SubdName )  "
    -> back_slash
back_slash: StringReplacer
    CASE = NO
    NO_MATCH = _FME_NO_OP_
    REGEXP = NO
    STR_REPLACE_TABLE = "_SubdName \\  "
    -> fwd_slash
fwd_slash: StringReplacer
    CASE = NO
    NO_MATCH = _FME_NO_OP_
    REGEXP = NO
    STR_REPLACE_TABLE = "_SubdName /  "
    -> Replace_Periods
Replace_Periods: StringReplacer
    CASE = NO
    NO_MATCH = _FME_NO_OP_
    REGEXP = NO
    STR_REPLACE_TABLE = "_SubdName .  "
    -> exclamation_sign
exclamation_sign: StringReplacer
    CASE = NO
    NO_MATCH = _FME_NO_OP_
    REGEXP = NO
    STR_REPLACE_TABLE = "_SubdName !  "
    -> question_sign
question_sign: StringReplacer
    CASE = NO
    NO_MATCH = _FME_NO_OP_
    REGEXP = NO
    STR_REPLACE_TABLE = "_SubdName ?  "
    -> FIRST_TO_1ST

Bookmark: Replace Spelled Out Numbers with Numbers (FIRST to 1ST)
FIRST_TO_1ST: StringReplacer
    CASE = NO
    NO_MATCH = _FME_NO_OP_
    REGEXP = YES
    STR_REPLACE_TABLE = _SubdName \bFIRST\b 1ST
    -> SECOND_TO_2ND
SECOND_TO_2ND: StringReplacer
    CASE = NO
    NO_MATCH = _FME_NO_OP_
    REGEXP = YES
    STR_REPLACE_TABLE = _SubdName \bSECOND\b 2ND
    -> THIRD_TO_3RD
THIRD_TO_3RD: StringReplacer
    CASE = NO
    NO_MATCH = _FME_NO_OP_
    REGEXP = YES
    STR_REPLACE_TABLE = _SubdName \bTHIRD\b 3RD
    -> FOURTH_TO_4TH
FOURTH_TO_4TH: StringReplacer
    CASE = NO
    NO_MATCH = _FME_NO_OP_
    REGEXP = YES
    STR_REPLACE_TABLE = _SubdName \bFOURTH\b 4TH
    -> FIFTH_TO_5TH
FIFTH_TO_5TH: StringReplacer
    CASE = NO
    NO_MATCH = _FME_NO_OP_
    REGEXP = YES
    STR_REPLACE_TABLE = _SubdName \bFIFTH\b 5TH
    -> SIXTH_TO_6TH
SIXTH_TO_6TH: StringReplacer
    CASE = NO
    NO_MATCH = _FME_NO_OP_
    REGEXP = YES
    STR_REPLACE_TABLE = _SubdName \bSIXTH\b 6TH
    -> SEVENTH_TO_7TH
SEVENTH_TO_7TH: StringReplacer
    CASE = NO
    NO_MATCH = _FME_NO_OP_
    REGEXP = YES
    STR_REPLACE_TABLE = _SubdName \bSEVENTH\b 7TH
    -> EIGTH_TO_8TH
EIGTH_TO_8TH: StringReplacer
    CASE = NO
    NO_MATCH = _FME_NO_OP_
    REGEXP = YES
    STR_REPLACE_TABLE = _SubdName \bEIGHTH\b 8TH
    -> NINTH_TO_9TH
NINTH_TO_9TH: StringReplacer
    CASE = NO
    NO_MATCH = _FME_NO_OP_
    REGEXP = YES
    STR_REPLACE_TABLE = _SubdName \bNINTH\b 9TH
    -> TENTH_TO_10TH
TENTH_TO_10TH: StringReplacer
    CASE = NO
    NO_MATCH = _FME_NO_OP_
    REGEXP = YES
    STR_REPLACE_TABLE = _SubdName \bTENTH\b 10TH
    -> 1_ST_TO_1ST

Bookmark: Address common formatting issues in ordinals
1_ST_TO_1ST: StringReplacer
    CASE = NO
    NO_MATCH = _FME_NO_OP_
    REGEXP = YES
    STR_REPLACE_TABLE = _SubdName \b1 ST\b 1ST
    -> 2_ND_TO_2ND
2_ND_TO_2ND: StringReplacer
    CASE = NO
    NO_MATCH = _FME_NO_OP_
    REGEXP = YES
    STR_REPLACE_TABLE = _SubdName \b2 ND\b 2ND
    -> 3_RD_TO_3RD
3_RD_TO_3RD: StringReplacer
    CASE = NO
    NO_MATCH = _FME_NO_OP_
    REGEXP = YES
    STR_REPLACE_TABLE = _SubdName \b3 RD\b 3RD
    -> 4_TH_TO_4TH
4_TH_TO_4TH: StringReplacer
    CASE = NO
    NO_MATCH = _FME_NO_OP_
    REGEXP = YES
    STR_REPLACE_TABLE = _SubdName \b4 TH\b 4TH
    -> 5_TH_TO_5TH
5_TH_TO_5TH: StringReplacer
    CASE = NO
    NO_MATCH = _FME_NO_OP_
    REGEXP = YES
    STR_REPLACE_TABLE = _SubdName \b5 TH\b 5TH
    -> 6_TH_TO_6TH
6_TH_TO_6TH: StringReplacer
    CASE = NO
    NO_MATCH = _FME_NO_OP_
    REGEXP = YES
    STR_REPLACE_TABLE = _SubdName \b6 TH\b 6TH
    -> 7_TH_TO_7TH
7_TH_TO_7TH: StringReplacer
    CASE = NO
    NO_MATCH = _FME_NO_OP_
    REGEXP = YES
    STR_REPLACE_TABLE = _SubdName \b7 TH\b 7TH
    -> 8_TH_TO_8TH
8_TH_TO_8TH: StringReplacer
    CASE = NO
    NO_MATCH = _FME_NO_OP_
    REGEXP = YES
    STR_REPLACE_TABLE = _SubdName \b8 TH\b 8TH
    -> 9_TH_TO_9TH
9_TH_TO_9TH: StringReplacer
    CASE = NO
    NO_MATCH = _FME_NO_OP_
    REGEXP = YES
    STR_REPLACE_TABLE = _SubdName \b9 TH\b 9TH
    -> 10_TH_TO_10TH
10_TH_TO_10TH: StringReplacer
    CASE = NO
    NO_MATCH = _FME_NO_OP_
    REGEXP = YES
    STR_REPLACE_TABLE = _SubdName \b10 TH\b 10TH
    -> remove_numbers

Bookmark: Replace numbers
remove_numbers: StringReplacer
    CASE = NO
    NO_MATCH = _FME_NO_OP_
    REGEXP = YES
    STR_REPLACE_TABLE = _SubdName \b(?:LT<pipe>LOT<pipe>BL(?:CK<pipe>K<pipe>OCK)<pipe>PH(?:ASE)?<pipe>AD(?:D<pipe>DITION<pipe>DN<pipe>DT)?<pipe>PA(?:R<pipe>RCEL)?<pipe>SEC(?:T<pipe>TION)?<pipe>TR(?:A<pipe>C<pipe>T)?<pipe>REV(?:ISION<pipe>ISED)?<pipe>COND(?:O<pipe>MINIUM)?<pipe>PAR(?:T)?<pipe>PT<pipe>AREA<pipe>FINAL<pipe>FN(?:L)?<pipe>PL(?:A<pipe>N)?<pipe>AMEN(?:D<pipe>DMENT)?<pipe>TW(?:P)?<pipe>TOWNSHIP<pipe>OUTL(?:INE)?<pipe>NO<pipe>PD)S?\b(\s*(\d+<pipe>ONE<pipe>TWO<pipe>THREE<pipe>FOUR<pipe>FIVE<pipe>SIX<pipe>SEVEN<pipe>EIGHT<pipe>NINE<pipe>TEN))\b<pipe>\bP\s*U\s*D\b ZZZ
    -> Roman_Numerals

Bookmark: Standardize roman numerals that are between spaces
Note: For I-1, an exemption is made to make sure that legitimate names like I-40 are not changed. Also added an exception for examples like X-L (extra large)
Roman_Numerals: Tester
    BOOL_OP = COMPOSITE
    COMPOSITE_TEST = 1 AND  NOT ( 2 OR 3 )
    TEST_CLAUSE:
      CASE_INSENSITIVE_TEST @Value(_SubdName) CONTAINS_REGEX \b(I|I(I)+|IV|V|V(I)+|IX|X)\b
      CASE_INSENSITIVE_TEST @Value(_SubdName) CONTAINS_REGEX I-(40|240|55|69)
      CASE_INSENSITIVE_TEST @Value(_SubdName) CONTAINS_REGEX X-L
    TEST_MODE = CASE_INSENSITIVE_TEST
    PASSED -> _I_
    FAILED -> Junction_4
_I_: StringReplacer
    CASE = NO
    NO_MATCH = _FME_NO_OP_
    REGEXP = YES
    STR_REPLACE_TABLE = _SubdName \bI\b 1
    -> _II_
_II_: StringReplacer
    CASE = NO
    NO_MATCH = _FME_NO_OP_
    REGEXP = YES
    STR_REPLACE_TABLE = _SubdName \bII\b 2
    -> _III_
_III_: StringReplacer
    CASE = NO
    NO_MATCH = _FME_NO_OP_
    REGEXP = YES
    STR_REPLACE_TABLE = _SubdName \bIII\b 3
    -> _IV_
_IV_: StringReplacer
    CASE = NO
    NO_MATCH = _FME_NO_OP_
    REGEXP = YES
    STR_REPLACE_TABLE = _SubdName \bIV\b 4
    -> _V_
_V_: StringReplacer
    CASE = NO
    NO_MATCH = _FME_NO_OP_
    REGEXP = YES
    STR_REPLACE_TABLE = _SubdName \bV\b 5
    -> _VI_
_VI_: StringReplacer
    CASE = NO
    NO_MATCH = _FME_NO_OP_
    REGEXP = YES
    STR_REPLACE_TABLE = _SubdName \bVI\b 6
    -> _VII_
_VII_: StringReplacer
    CASE = NO
    NO_MATCH = _FME_NO_OP_
    REGEXP = YES
    STR_REPLACE_TABLE = _SubdName \bVII\b 7
    -> _VIII_
_VIII_: StringReplacer
    CASE = NO
    NO_MATCH = _FME_NO_OP_
    REGEXP = YES
    STR_REPLACE_TABLE = _SubdName \bVIII\b 8
    -> _IX_
_IX_: StringReplacer
    CASE = NO
    NO_MATCH = _FME_NO_OP_
    REGEXP = YES
    STR_REPLACE_TABLE = _SubdName \bIX\b 9
    -> _X_
_X_: StringReplacer
    CASE = NO
    NO_MATCH = _FME_NO_OP_
    REGEXP = YES
    STR_REPLACE_TABLE = _SubdName \bX\b 10
    -> Junction_5
Junction_4
    -> Junction_5
Junction_5
    -> Check_Again_3

Bookmark: Remove Extra Spaces for _SubdName
Note: Then check to see if any more spaces are found
Check_Again_3: Tester
    BOOL_OP = OR
    TEST_CLAUSE = CASE_INSENSITIVE_TEST @Value(_SubdName) CONTAINS_REGEX
    TEST_MODE = CASE_INSENSITIVE_TEST
    PASSED -> Clean_Spaces_3
    FAILED -> Junction_3
Clean_Spaces_3: StringReplacer
    CASE = NO
    NO_MATCH = _FME_NO_OP_
    REGEXP = NO
    STR_REPLACE_TABLE = "_SubdName     "
    -> trim_end_spaces
Note: Replace double spaces with single spaces. Trim ends as well
trim_end_spaces: AttributeTrimmer
    SRC_ATTRS = _ParcelID,_SubdName
    TRIM_CHARS = " "
    TRIM_TO_NONE = Yes
    TRIM_TYPE = BOTH
    -> Junction_32
Junction_3
    -> Junction_32
